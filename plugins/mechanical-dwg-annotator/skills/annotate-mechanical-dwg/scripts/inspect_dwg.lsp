(defun ad:pt (p) (strcat (rtos (car p) 2 6) "," (rtos (cadr p) 2 6) "," (rtos (if (caddr p) (caddr p) 0.0) 2 6)))
(defun ad:field (data code / value)
  (setq value (cdr (assoc code data)))
  (cond ((null value) "") ((listp value) (ad:pt value)) ((numberp value) (rtos value 2 6)) (T value)))
(defun c:DWGINSPECT (/ out path ss idx ent data count typ layer handle)
  (setq path (getenv "CODEX_DWG_REPORT"))
  (if (or (null path) (= path "")) (setq path (strcat (getvar "DWGPREFIX") "dwg-report.tsv")))
  (setq out (open path "w"))
  (write-line (strcat "drawing\t" (getvar "DWGNAME")) out)
  (write-line (strcat "insunits\t" (itoa (getvar "INSUNITS"))) out)
  (write-line (strcat "measurement\t" (itoa (getvar "MEASUREMENT"))) out)
  (write-line "type\tlayer\thandle\tpoint10\tpoint11\tradius40\tangle50\tangle51" out)
  (setq count 0)
  (setq ss (ssget "_X") idx 0)
  (if ss
    (repeat (sslength ss)
      (setq ent (ssname ss idx) data (entget ent))
      (setq typ (cdr (assoc 0 data)) layer (cdr (assoc 8 data)) handle (cdr (assoc 5 data)))
      (write-line (strcat typ "\t" layer "\t" handle "\t" (ad:field data 10) "\t" (ad:field data 11) "\t" (ad:field data 40) "\t" (ad:field data 50) "\t" (ad:field data 51)) out)
      (setq count (1+ count) idx (1+ idx))))
  (write-line (strcat "entity_count\t" (itoa count)) out)
  (close out)
  (princ (strcat "\nCODEX_DWG_REPORT=" path "\n")) (princ))
